module sonic-bgp-device-global {
    namespace "http://github.com/sonic-net/sonic-bgp-device-global";
    prefix bgp_device_global;
    yang-version 1.1;

    organization
        "SONiC";

    contact
        "SONiC";

    description
        "SONIC Device-specific BGP global data";

    revision 2022-06-26 {
        description
            "Initial revision";
    }

    container sonic-bgp-device-global {
        container BGP_DEVICE_GLOBAL {
            container STATE {
                description "BGP device-specific global data";
                leaf tsa_enabled {
                    type enumumeration {
                        enum all {
                            description "This field is set when traffic is shifted away (TSA) from all BGP neighbors,
                            i,e, BGP routes are not advertised to iBGP or eBGP neighbors"                            
                        }
                        enum none {
                            description "This field is set when traffic is shifted back (TSB) to all BGP neighbors,
                            i,e, BGP routes are advertised to all iBGP and eBGP neighbors" 
                        }
                        enum external-only {
                            description "This field is set when traffic is shifted away from external BGP neighbors only,
                            i,e, BGP routes are advertised to iBGP neighbors, but not to eBGP neighbors" 
                        }
                    }
                    default none
                }
            } /* end of STATE container */
        } /* end of BGP_DEVICE_GLOBAL container */

    } /* end of top level container */

} /* end of module sonic-bgp-device-global */
